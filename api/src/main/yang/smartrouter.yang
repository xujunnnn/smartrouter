module smartrouter {
    yang-version 1;
    namespace "urn:opendaylight:params:xml:ns:yang:smartrouter";
    prefix "smartrouter";

    revision "2015-01-05" {
        description "Initial revision of smartrouter model";
    }
    container Traffic_Requirments{
    	list requirements{
    		key "name";
    		leaf name{
    			type string;
    		}
    		leaf BW{
    			type uint32;
    		}
    		leaf delay{
    			type uint32;
    		}
    		leaf priority{
    			type uint8;
    		}
    		
    	}
    	
    }
}
